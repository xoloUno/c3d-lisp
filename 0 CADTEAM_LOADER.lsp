; CAD Team AutoLISP Loader
; Loaded by acaddoc.lsp for every opened or newly created drawing.

(defun _cadteam-load (filename / filepath result)
  (setq filepath (findfile filename))
  (cond
    ((null filepath)
      (princ (strcat "\nCAD Team Loader: NOT FOUND - " filename)))
    (T
      (setq result (vl-catch-all-apply 'load (list filepath)))
      (if (vl-catch-all-error-p result)
        (princ (strcat "\nCAD Team Loader: FAILED - " filename))
        (princ (strcat "\nCAD Team Loader: loaded " filename))
      )
    )
  )
)

(defun c:CADHELP (/)
  (textscr)
  (princ "\nCAD TEAM COMMANDS")
  (princ "\n-----------------")
  (princ "\nCADHELP       Show this command list.")
  (princ "\nBATCH-BLOCK-REPLACE-PICK  Replace selected paper-space blocks across target DWGs. Back up and test first.")
  (princ "\nCADSETCHECK   Report current CAD and drafting settings without changing them.")
  (princ "\nCADSETTINGS   Apply agreed performance, plotting, and DIMASSOC settings.")
  (princ "\nDRAFTSETTINGS Apply standardized OSNAP, polar, 3D OSNAP, and selection settings.")
  (princ "\nFINDNONZERO   Select and report model-space objects with nonzero Z or 3D geometry.")
  (princ "\nFINDTILT      Select and report tilted model-space objects by object type.")
  (princ "\nFLATALL       Flatten common 2D model-space objects to Z=0 and fix slight tilt.")
  (princ "\nFLATDIMS      Flatten dims, leaders, and mleaders to Z=0 and fix UCS grip errors.")
  (princ "\nFLATMORE      Flatten remaining strongly tilted lightweight polylines after review.")
  (princ "\nFLATHATCH     Rebuild tilted hatches flat at Z=0.")
  (princ "\nFLATPOINTS    Flatten reviewed points within a Z range; default cutoff is +/-5.0.")
  (princ "\nFLAT3DPOLY    Convert reviewed 3D polylines to lightweight 2D polylines at Z=0.")
  (princ "\nXRINDEX       Set INDEXCTL=3 in the active source XREF; save afterward.")
  (princ "\nZEROBAR       Clean drawing: ZERO, Blocks, Regapps, Audit, Blocks, Regapps.")
  (princ)
)

(_cadteam-load "ZEROBAR_Cleanup.lsp")
(_cadteam-load "CADSETTINGS_v4.lsp")
(_cadteam-load "batch-block-replace-pick.lsp")
(_cadteam-load "FLATDIMS.lsp")
(_cadteam-load "FLATALL.lsp")
(_cadteam-load "FLATMORE.lsp")
(_cadteam-load "FLAT3DPOLY.lsp")

(princ "\nCAD Team Loader complete. Type CADHELP for available commands.")
(princ)
