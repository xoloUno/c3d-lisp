; CAD Settings Utility v4
; Commands:
;   CADSETTINGS   - Applies agreed optimization/output settings.
;   DRAFTSETTINGS - Applies standardized drafting preferences.
;   XRINDEX       - Sets INDEXCTL=3 in the active source XREF DWG.
;   CADSETCHECK   - Reports current values without changing anything.

(defun _cadset-safe (name value / result)
  (setq result (vl-catch-all-apply 'setvar (list name value)))
  (if (vl-catch-all-error-p result)
    (princ (strcat "\n  SKIPPED " name " (not available or locked)"))
    (princ (strcat "\n  " name " = " (vl-princ-to-string (getvar name))))
  )
)

(defun _cadset-show (name / result)
  (setq result (vl-catch-all-apply 'getvar (list name)))
  (if (vl-catch-all-error-p result)
    (princ (strcat "\n  " name " = unavailable"))
    (princ (strcat "\n  " name " = " (vl-princ-to-string result)))
  )
)

(defun c:CADSETTINGS (/)
  (princ "\nApplying agreed AutoCAD optimization/output settings...")
  (_cadset-safe "LAYEREVALCTL" 0)
  (_cadset-safe "XREFREGAPPCTL" 1)
  (_cadset-safe "DIMASSOC" 2)
  (_cadset-safe "BACKGROUNDPLOT" 0)
  (_cadset-safe "PDFSHX" 0)
  (_cadset-safe "MIRRTEXT" 0)
  (princ "\nCAD settings applied. DIMASSOC and MIRRTEXT are stored in the active drawing; the other settings are user/profile settings.")
  (princ "\nUse XRINDEX separately inside source XREF DWGs.")
  (princ)
)

(defun c:DRAFTSETTINGS (/)
  (princ "\nApplying standardized drafting preferences...")
  (_cadset-safe "OSMODE" 4143)
  (_cadset-safe "AUTOSNAP" 47)
  (_cadset-safe "POLARANG" (/ pi 2.0))
  (_cadset-safe "POLARMODE" 0)
  (_cadset-safe "SELECTIONCYCLING" -2)
  (_cadset-safe "3DOSMODE" 17551)
  (princ "\nDraft settings applied. Running 2D and 3D Nearest snaps are excluded.")
  (princ "\n3D object snaps are off; approved 3D and point-cloud modes are stored.")
  (princ)
)

(defun c:XRINDEX (/)
  (princ "\nSetting layer and spatial indexes in the active drawing...")
  (_cadset-safe "INDEXCTL" 3)
  (princ "\nSave this source XREF DWG to store the indexes.")
  (princ)
)

(defun c:CADSETCHECK (/)
  (princ "\nCurrent AutoCAD production settings:")
  (_cadset-show "LAYEREVALCTL")
  (_cadset-show "XREFREGAPPCTL")
  (_cadset-show "DIMASSOC")
  (_cadset-show "BACKGROUNDPLOT")
  (_cadset-show "PDFSHX")
  (_cadset-show "MIRRTEXT")
  (_cadset-show "INDEXCTL")
  (_cadset-show "OSMODE")
  (_cadset-show "AUTOSNAP")
  (_cadset-show "POLARANG")
  (_cadset-show "POLARMODE")
  (_cadset-show "SELECTIONCYCLING")
  (_cadset-show "3DOSMODE")
  (princ)
)

(princ "\nCAD Settings Utility v4 loaded. Commands: CADSETTINGS, DRAFTSETTINGS, XRINDEX, CADSETCHECK.")
(princ)
